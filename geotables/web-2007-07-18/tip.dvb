Attribute VB_Name = "UserFormTip"
Attribute VB_Base = "0{568C7FF2-64FA-4B8D-847C-45D0788A495E}{53F5553A-B040-4219-A720-BE8AEF772DAB}"
Attribute VB_GlobalNameSpace = False
Attribute VB_Creatable = False
Attribute VB_PredeclaredId = True
Attribute VB_Exposed = False
Attribute VB_TemplateDerived = False
Attribute VB_Customizable = False
' TIP.DVB
'
' Copyright 2005 Thomas Gail Haws
' This program is free software under the terms of the
' GNU (GNU--acronym for Gnu's Not Unix--sounds like canoe)
' General Public License as published by the Free Software Foundation,
' version 2 of the License.
'
' You can redistribute this software for any fee or no fee and/or
' modify it in any way, but it and ANY MODIFICATIONS OR DERIVATIONS
' continue to be governed by the license, which protects the perpetual
' availability of the software for free distribution and modification.
'
' You CAN'T put this code into any proprietary package.  Read the license.
'
' If you improve this software, please make a revision submittal to the
' copyright owner at www.hawsedc.com.
'
' This program is distributed in the hope that it will be useful,
' but WITHOUT ANY WARRANTY; without even the implied warranty of
' MERCHANTABILITY or FITNESS FOR A PARTICULAR PURPOSE.  See the
' GNU General Public License on the World Wide Web for more details.

Private Sub CheckBoxShowAgain_Change()
    If CheckBoxShowAgain.Value = False Then
    strShowAgain = "BooleanFalse"
    Else
    strShowAgain = "BooleanTrue"
    End If
End Sub
Private Sub CommandButtonOK_Click()
    Unload Me
End Sub

Attribute VB_Name = "modTip"
Option Explicit
Public strShowAgain As String
Public strTip As String

'Requires AutoCAD setvar/getvars
'users1 = Tip text in and checkbox value out
Sub Tip()
    Dim objThisDrawing As AcadDocument
    Dim strTip As String
        
    Set objThisDrawing = AutoCAD.Application.ActiveDocument
    strTip = objThisDrawing.GetVariable("users1")
    
    Dim frmTip As UserFormTip
    Set frmTip = New UserFormTip
    frmTip.CheckBoxShowAgain.Value = True
    frmTip.TextBoxTip.Value = strTip
    frmTip.Show
    Set frmTip = Nothing
    objThisDrawing.SetVariable "users1", strShowAgain
End Sub
