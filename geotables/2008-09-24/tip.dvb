Attribute VB_Name = "UserFormTip"
Attribute VB_Base = "0{F3B8FAF8-C560-49A0-8487-84A625C9953C}{1205DA7C-C70B-43FB-8796-3F4250C9A26B}"
Attribute VB_GlobalNameSpace = False
Attribute VB_Creatable = False
Attribute VB_PredeclaredId = True
Attribute VB_Exposed = False
Attribute VB_TemplateDerived = False
Attribute VB_Customizable = False
Private Sub CheckBoxShowAgain_Change()
    If CheckBoxShowAgain.Value = False Then
    strShowAgain = "BooleanFalse"
    Else
    strShowAgain = "BooleanTrue"
    End If
End Sub
Private Sub CommandButtonOK_Click()
    Unload Me
End Sub

Attribute VB_Name = "modTip"
Option Explicit
Public strShowAgain As String
Public strTip As String

'Requires AutoCAD setvar/getvars
'users1 = Tip text in and checkbox value out
Sub Tip()
    Dim objThisDrawing As AcadDocument
    Dim strTip As String
        
    Set objThisDrawing = AutoCAD.Application.ActiveDocument
    strTip = objThisDrawing.GetVariable("users1")
    
    Dim frmTip As UserFormTip
    Set frmTip = New UserFormTip
    frmTip.CheckBoxShowAgain.Value = True
    frmTip.TextBoxTip.Value = strTip
    frmTip.Show
    Set frmTip = Nothing
    objThisDrawing.SetVariable "users1", strShowAgain
End Sub
