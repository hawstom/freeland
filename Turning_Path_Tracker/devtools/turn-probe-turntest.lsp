;;; turn-probe-turntest.lsp - rerun Tom's turntest.dwg case (tom5 on course 54B3) unattended.
;;; Copies the course and the vehicle block out of the drawing with ObjectDBX. Probe; never ships.
(defun turn-probe-tt-run (/ atts blk copies course dbx en-course en-vehicle heading paths rig ss)
  (setq dbx (turn-tool-outside-dbx))
  (turn-test-write (strcat "- dbx " (vl-princ-to-string dbx)))
  (vla-open dbx (turn-test-src "turntest.dwg"))
  (vlax-for obj (vla-get-modelspace dbx)
    (cond ((= "54B3" (vla-get-handle obj)) (setq en-course obj))
          ((and (= "AcDbBlockReference" (vla-get-objectname obj)) (wcmatch (strcase (vla-get-name obj)) "*TOM5"))
           (setq blk obj))))
  (turn-test-write (strcat "- found course " (vl-princ-to-string en-course) " block " (vl-princ-to-string blk)))
  (setq
    copies (vla-CopyObjects dbx
             (vlax-make-variant (vlax-safearray-fill (vlax-make-safearray vlax-vbObject '(0 . 1)) (list en-course blk)))
             (vla-get-ModelSpace (vla-get-ActiveDocument (vlax-get-acad-object))))
    copies (vlax-safearray->list (vlax-variant-value copies))
  )
  (vlax-release-object dbx)
  (foreach c copies
    (if (= "AcDbBlockReference" (vla-get-objectname c))
      (setq en-vehicle (vlax-vla-object->ename c))
      (setq en-course (vlax-vla-object->ename c))))
  (setq
        atts (turn-block-attributes en-vehicle)
        rig (turn-vehicle-from-attributes atts)
        heading (+ pi (cdr (assoc 50 (entget en-vehicle)))))
  (turn-test-write (strcat "- rig: " (vl-princ-to-string rig)))
  (turn-test-write (strcat "- block at " (vl-princ-to-string (cdr (assoc 10 (entget en-vehicle)))) " heading " (rtos heading 2 4)))
  (setq course (turn-course-from-curve en-course '(1224.9 315.3) (turn-default-step rig)))
  (turn-test-write (strcat "- step " (rtos (turn-default-step rig) 2 3) ", " (itoa (length course)) " course points"))
  (turn-probe-tt-case "as Tom ran it" rig course heading)
  (turn-probe-tt-case "heading along the course" rig course (angle (car course) (cadr course)))
)
(defun turn-probe-tt-count (label / ss)
  (foreach ty '("REGION" "LWPOLYLINE")
    (setq ss (ssget "_X" (list (cons 0 ty) '(8 . "C-TURN-ENVL"))))
    (turn-test-write (strcat "- " label ": " ty " on C-TURN-ENVL: " (itoa (if ss (sslength ss) 0))))))
;; turn-run's own report, captured.
(defun turn-test-punch-capture-report-run (rig course heading / real result)
  (setq *turn-test-punch-said* "" real princ)
  (defun princ (s) (if (= 'STR (type s)) (setq *turn-test-punch-said* (strcat *turn-test-punch-said* s))) s)
  (setq result (vl-catch-all-apply 'turn-run (list rig course heading 10)))
  (setq princ real)
  (if (vl-catch-all-error-p result) (turn-test-write (strcat "- turn-run raised: " (vl-catch-all-error-message result))))
  (turn-test-write "```")
  (turn-test-write *turn-test-punch-said*)
  (turn-test-write "```")
)

(defun turn-probe-tt-case (label rig course heading / area ss t0)
  (if (setq ss (ssget "_X" '((8 . "C-TURN-*")))) (command "._erase" ss ""))
  (turn-test-write (strcat "### " label ", heading " (rtos heading 2 4)))
  (setq t0 (getvar "millisecs")
        area (vl-catch-all-apply 'turn-draw-envelope (list rig (turn-path rig course heading))))
  (turn-test-write (strcat "- envelope in " (rtos (/ (- (getvar "millisecs") t0) 1000.0) 2 1) " s, area "
                           (vl-princ-to-string area)))
  (turn-probe-tt-count label)
)
