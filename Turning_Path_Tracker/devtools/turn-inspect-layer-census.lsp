;;; turn-inspect-layer-census.lsp - every object on every C-TURN-* layer, by type. Tool; never ships.
(vl-load-com)
(defun turn-tool-census-run (dwg log / dbx f key tally rec)
  (setq dbx (turn-tool-outside-dbx))
  (vla-open dbx dwg)
  (vlax-for obj (vla-get-modelspace dbx)
    (if (and (not (wcmatch (vla-get-layer obj) "C-TURN-*"))
             (vlax-property-available-p obj 'Length))
      (setq tally (cons (cons (strcat "OTHER " (vla-get-layer obj) " " (vla-get-objectname obj) " len "
                                      (rtos (vla-get-length obj) 2 2) " from "
                                      (vl-princ-to-string (mapcar '(lambda (x) (atof (rtos x 2 2))) (vlax-curve-getStartPoint obj)))
                                      " to " (vl-princ-to-string (mapcar '(lambda (x) (atof (rtos x 2 2))) (vlax-curve-getEndPoint obj)))
                                      " handle " (vla-get-handle obj)) 1) tally)))
    (if (wcmatch (vla-get-layer obj) "C-TURN-*")
      (progn
        (setq key (strcat (vla-get-layer obj) " " (vla-get-objectname obj)))
        (if (setq rec (assoc key tally))
          (setq tally (subst (cons key (1+ (cdr rec))) rec tally))
          (setq tally (cons (cons key 1) tally)))
      )
    )
  )
  (vlax-release-object dbx)
  (setq f (open log "w"))
  (write-line (strcat "# C-TURN-* census: " dwg) f)
  (foreach r (vl-sort tally '(lambda (a b) (< (car a) (car b))))
    (write-line (strcat "- " (car r) ": " (itoa (cdr r))) f))
  (close f)
)
